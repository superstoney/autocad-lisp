(defun c:BoundingBoxRectangle ()
  (setq poly (car (entsel "\n请选择一个多边形: ")))
  (if (and poly (= (cdr (assoc 0 (entget poly))) "LWPOLYLINE"))
    (progn
      (setq vertices (vl-remove-if 'listp (mapcar 'cdr (vl-remove-if-not '(lambda (x) (= (car x) 10)) (entget poly)))))
      (setq min-x (apply 'min (mapcar 'car vertices)))
      (setq max-x (apply 'max (mapcar 'car vertices)))
      (setq min-y (apply 'min (mapcar 'cadr vertices)))
      (setq max-y (apply 'max (mapcar 'cadr vertices)))
      (command "_.PLINE" (list min-x min-y) (list max-x min-y) (list max-x max-y) (list min-x max-y) (list min-x min-y) "")
    )
    (princ "\n选择的对象不是多边形.")
  )
  (princ)
)

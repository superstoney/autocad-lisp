(defun get-path-self(/ get-path-ap get-path-drag lastload)
	(defun get-path-drag(lastload / file str)
		(setq str (vl-string-search "(LOAD \"" lastload))
		(setq file (substr lastload (+ str 8) (- (vl-string-search "\")" lastload) str 7)))
		(setq file (vl-string-translate "/" "\\" file))
		(vl-filename-directory file)
	)
	(defun get-path-ap(/ file reg-key)
		(setq reg-key (strcat "HKEY_CURRENT_USER\\" (vlax-product-key) "\\Profiles\\" (getvar "cprofile") "\\Dialogs\\Appload"))
		(setq file (vl-registry-read reg-key "MainDialog"))
		(vl-string-right-trim "\\\\" file)
	)
	(princ "\n")
	(cond
		((and
			 (setq lastload (getvar "lastprompt"))
			 (wcmatch (strcase lastload) "*LOAD \"*")
		 )
			(get-path-drag lastload)
		)
		(t (get-path-ap))
	)
)
(vl-load-com)
(cond
	((or *FSTL_DIR* (setq *FSTL_DIR* (get-path-self)))
		(load (findfile (strcat *FSTL_DIR* "\\Program\\UNSETUP.lsp")))
		(av:unsetup)
	)
	(T (alert "无法卸载，请直接删除AVTLS文件夹！"))
)

(vl-load-com)
;特殊标注与说明
(defun c:Label-A (/ *error* dclid e_lst fn fname key)
	(setq e_lst(mapcar(function(lambda(n)(list 'setvar n (getvar n)))) '("cmdecho")))
	(defun *error* (msg)(mapcar 'eval e_lst))
	;(princ "-->特殊标注符号")
	(setvar "cmdecho" 0)
	(setq fname (av:findfile "label.dcl"))
	(setq fn (open fname "r"))
	(setq dclid (load_dialog fname))
	(new_dialog "label" dclid "")
	(action_tile "111" "(done_dialog 111)")
	;(action_tile "112" "(done_dialog 112)")
	(action_tile "121" "(done_dialog 121)")
	(action_tile "122" "(done_dialog 122)")
	(action_tile "131" "(done_dialog 131)")
	(action_tile "132" "(done_dialog 132)")
	(action_tile "211" "(done_dialog 211)")
	(action_tile "221" "(done_dialog 221)")
	(action_tile "231" "(done_dialog 231)")
	(setq key (start_dialog))
	(unload_dialog dclid)
	(close fn)
	(cond
		((= key 111)
			(cond (c:numinc)(t (load (av:findfile "numinc.lsp"))))
			(vla-SendCommand *doc* "numinc ")
		)
		((= key 121)
			(cond (c:NBT_zbbz) (t (load (av:findfile "NBT_zbbz.VLX"))))
			(vla-SendCommand *doc* "NBT_zbbz ")
		)
		((= key 122)
			(cond (C:fsxmzbbz) (t (load (av:findfile "fsxm_dimpointid.VLX"))))
			(vla-SendCommand *doc* "fsxmzbbz ")
		)
		((= key 131)
			(cond (c:bgbz) (t (load (av:findfile "bgbz.lsp"))))
			(vla-SendCommand *doc* "bgbz ")
		)
		((= key 211)(vla-SendCommand *doc* "jt1 "))
		((= key 222)(vla-SendCommand *doc* "jt2 "))
		((= key 233)(vla-SendCommand *doc* "ArrowHead "))
	)
	(*error* nil)
	;(setvar "cmdecho" 1)
	(princ)
)
;;======================================================================================
;;实心箭头
(defun c:jt1(/ ang h l0 p0 p1 p2 ss sys)
  (setvar "cmdecho" 0)	
  (setq sys (getvar "osmode"))
  (setvar "osmode" 0)
	(setq p0(getpoint "\n请输入起点：")
		p1(getpoint p0 "\n请输入终点：")
		l0(distance p1 p0)
		ang(angle p0 p1)
		p2(polar p0 ang (* 0.75 l0));箭头长度占总长的0.25
		h(* l0 0.02);直线的宽度占总长的0.02
	)
	(setq ss (ssadd))
	(command "pline" p0 "H" h h p2 "")
	(setq ss (ssadd (entlast) ss))
	(command "pline" p2 "H" (* h 3) 0 p1 "");箭头的宽度是直线部分的3倍
	(setq ss (ssadd (entlast) ss))
  (command "pedit" "m" ss "" "j" "" "")
  (setvar "osmode" sys)
	(setvar "cmdecho" 1)
	(prin1)
)
;(princ "\n-->实体箭头JT")

;空心箭头
(defun c:jt2 (/ ang ang1 l0 l1 p0 p1 p2 p3 p4 ss sys tan);;;绘制出的箭头是空心且整体的。
	(setvar "cmdecho" 0)
	(defun tan (a) (/ (sin a)(cos a)))
  (setq sys (getvar "osmode"))
  (setvar "osmode" 0)
  (setq p0 (getpoint "\n请输入基准点：")
		p1   (getpoint p0 "\n请输入第二点：")
		l0   (distance p0 p1)
		ang  (angle p0 p1)
		l1   (* 0.18 l0);此系数可调，用于调整箭头区占整个箭头的长度，0.18是系数
		ang1 (* 0.08333333 pi);箭头的角度为30度
		p2   (polar p0 (+ ang (* 0.5 pi)) (* 0.35 (* l1 (tan ang1))));定义箭尾的宽度，0.35是系数
		p3   (polar p2 ang (- l0 l1))
		p4   (polar p3 (+ ang (* 0.5 pi)) (* l1 (tan ang1)))
	)
  (setq ss (ssadd))
  (command "pline" p0 p2 p3 p4 p1 "")
  (setq ss (ssadd (entlast) ss))
  (command "mirror" ss "" p0 p1 "N")
  (setq ss (ssadd (entlast) ss))
  (command "pedit" "m" ss "" "j" "" "")
  (setvar "osmode" sys)
	(setvar "cmdecho" 1)
  (prin1)
)
;(princ "+空心箭头JT2")

(defun c:ArrowHead (/ an dd enda p1 p2 p3 p4 w)
  (setvar "cmdecho" 0)
  (initget "A B C")
  (setq	enda (getkword "\n绘制箭头[直箭头(A)/弯箭头(B)/大弯箭头(C)]<直箭头>:"))
  (or enda (setq enda "A"))
  (while (and 
					 (setq p1 (getpoint "\n箭头的尖端位置:"))
					 (setq p2 (getpoint p1 "\n箭头的另一端:"))
				 )
    (setq dd (distance p1 p2))
    (princ (rtos dd 2 4))
    (setq 
			w  (* dd 1.2)
			an (angle p1 p2)
			p3 (polar p2 (+ an (* pi 0.5)) (/ w 2.0))
			p4 (polar p2 (+ an (* pi 1.5)) (/ w 2.0))
		)
    (command ".pline" p1 "w" "0" w p2 "w")
    (cond 
			((= enda "A")
				(command (* w 0.4) (* w 0.4))
				(fstl_sendcmd (strcat "<" (angtos (angle p1 p2) 0 1)))
				(command (polar p2 an (getdist p2 "\n指定端点：")) "")
			)
			((= enda "B")
				(command (* w 0.4) (* w 0.4) "a" "\\" "")
			)
			((= enda "C")
				(command (* w 0.4) w "a" "\\" "")
			)
		)
	)
  (princ)
)

(princ)
